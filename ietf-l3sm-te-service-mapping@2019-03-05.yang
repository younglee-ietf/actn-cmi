module ietf-l3sm-te-service-mapping {

       namespace "urn:ietf:params:xml:ns:yang:ietf-l3sm-te-service-mapping";

       prefix "tm";

       import ietf-te-service-mapping-types {
	  prefix "tsm-types";
       }
	   
       import ietf-l3vpn-svc {
          prefix "l3vpn-svc";
       }

       organization
           "IETF Traffic Engineering Architecture and Signaling (TEAS)
           Working Group";

       contact
           "Editor: Young Lee <leeyoung@huawei.com>
                    Dhruv Dhody <dhruv.ietf@gmail.com>
		    Qin Wu <bill.wu@huawei.com>";
       description
           "This module contains a YANG module for the mapping of
           Layer 3 Service Model (L3SM) to the TE and VN ";

       revision 2019-03-05 {
           description
               "initial version.";
           reference
               "TBD";
       }

       /*
        * Configuration data nodes
        */
       augment "/l3vpn-svc:l3vpn-svc/l3vpn-svc:vpn-services/l3vpn-svc:vpn-service" {
	 description
           "l3sm augmented to include TE parameters and mapping";
	   container te-service-mapping {
              presence "indicates l3 service to te mapping";
              description
                "Container to augment l3sm to TE parameters and mapping";	
           }
       }
	   
       augment "/l3vpn-svc:l3vpn-svc/l3vpn-svc:vpn-services/l3vpn-svc:vpn-service" {
         description 
           "This augment is only valid for TE mapping --
            te mapping is added"; 
         uses tsm-types:te-mapping;
       }
	   
       augment "/l3vpn-svc:l3vpn-svc/l3vpn-svc:sites/l3vpn-svc:site"
	      +"/l3vpn-svc:site-network-accesses/l3vpn-svc:site-network-access" {
	 description 
           "This augment is only valid for TE mapping --
            network-access te-reference is added"; 
	 uses tsm-types:te-endpoint-ref;
       }
   }
