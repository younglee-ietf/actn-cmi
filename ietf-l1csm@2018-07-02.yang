module ietf-l1csm {
  yang-version 1.1;
  namespace "urn:ietf:params:xml:ns:yang:ietf-l1csm";
		 
  prefix "l1csm";
  import ietf-yang-types {
    prefix "yang";  
  }

  import ietf-l1-mef-service-types {
    prefix "l1-st";
  }
		
  organization
    "Internet Engineering Task Force (IETF) CCAMP WG";
			
  contact
                        
    "Editor: G. Fioccolla (giuseppe.fioccola@telecomitalia.it)
     Editor: K. Lee (kwangkoog.lee@kt.com)
     Editor: Y. Lee (leeyoung@huawei.com)
     Editor: D. Dhody (dhruv.ietf@gmail.com)
     Editor: O. G. de-Dios (oscar.gonzalezdedios@telefonica.com)
     Editor: D. Ceccarelli (daniele.ceccarelli@ericsson.com)";

				
  description
    "this module describes Layer 1 connectivity service 
     model for subscriber Layer 1 Connectivity Services 
     and Attributes. Refer to 'MEF x.y.x Technical Specification 
     Working Draft v0.09 5, December 13, 2017' for all terms and
     the original references used in the module. 

     Copyright (c) 2018 IETF Trust and the persons identified as
     authors of the code.  All rights reserved.
     Redistribution and use in source and binary forms, with or
     without modification, is permitted pursuant to, and subject
     to the license terms contained in, the Simplified BSD 
     License set forth in Section 4.c of the IETF Trust's Legal 
     Provisions Relating to IETF Documents
     (http://trustee.ietf.org/license-info).

     This version of this YANG module is part of RFC XXXX; see
     the RFC itself for full legal notices.";

revision 2018-07-02 {
    description 
	"updated version to incorporate MEF comments";
	 reference "to add the draft name"; 
  }
  
revision 2018-06-20 {
    description 
	"updated version to incorporate MEF comments";
	 reference "to add the draft name"; 
  }
		
  revision 2018-04-11 {
    description
      "Initial revision.";
       reference "to add the draft name";         
  }

		
  grouping protocol-coding-optical_interface {
    description
	 "describes <p,c,o> where p:protocol type; c:coding 
       function; o:optical interface function";
	 leaf protocol {
	   type identityref {
	     base "l1-st:protocol-type";
	   }
	   description 
          "List of physical layer L1VC clientprotocol";
	 }
	 leaf coding {
	    type identityref {
		 base "l1-st:coding-func";
	    }
	    description "coding function";
	 }
       leaf optical_interface {
	    type identityref {
		 base "l1-st:optical-interface-func";
	    }
						
	    description "optical-interface-function";
	  }		
	}
		
  grouping uni-attributes {
    description
	 "uni-service-attributes";
						
	 leaf UNI-ID {
	   type string;
	   description "the UNI id of UNI Service Attributes";
	 }
						
	 uses protocol-coding-optical_interface; 				
  }

  grouping subscriber-l1vc-sls-service-attribute {
    description
	 "The value of the Subscriber L1VC SLS (Service Level 
        Specification) Service Attribute expressed in a 3-tuple
        <p,c,o> of the form.";
						
	 leaf time-start {
	   type yang:date-and-time;
	   description "a time that represent the date and time 
                     for the start of the SLS";
	 }
						
	 leaf time-interval {
	   type int16;
	   units seconds; 
	   description "a time interval (e.g., 2,419,200 seconds 
                     which is 28 days) that is used in  
                     conjunction wuth time-start to specify a 
                     contiguous sequence of time intervals T for 
                     determining when performance objectives are 
                     met.";
	 }				
												
	 leaf performance-metric {
	   type identityref {
	     base "l1-st:performance-metriclist";
	   }
	   description "list of performance metric";
	 }
  }
		
  grouping subscriber-l1vc-service-attributes {
    description
	 "subscriber layer 1 connection service service level";
				
	 leaf subscriber-l1vc-id {
	   type string;
	   description "subscriber L1VC identifier";
	 }
				
	 leaf subscriber-l1vc-ep-id-1 {
	   type string;
	   description "subscriber end point ID of one end";
	 }
				
	 leaf subscriber-l1vc-ep-id-2 {
	   type string;
	   description "subscriber end point ID of the other end";
	 }
				
	 leaf subscriber-l1vc-ep-UNI-1 {
	   type leafref {
	   path "/l1cs/access/uni-list/UNI-ID";
	   }
	 description "this is one end of subscriber L1VC end point 
                   ID value = UNI-1"; 
	 }
						
	 leaf subscriber-l1vc-ep-UNI-2 {
	   type leafref {
	   path "/l1cs/access/uni-list/UNI-ID";
	   }
	 description "this is the other end of subscriber L1VC end 
                    point ID value = UNI-2"; 
	 }
								
	 uses subscriber-l1vc-sls-service-attribute;
  }
		
  grouping subscriber-attributes {
    description
	 "subscriber attributes";
				
	 uses subscriber-l1vc-service-attributes;
  }
		
  container l1cs {
    description
      "serves as a top-level container for a list of layer 1 
       connection services (l1cs)";

	 container access {
	   description "UNI configurations";
					
	   list uni-list {
	     key "UNI-ID";
	     description "uni identifier";
		  uses uni-attributes {
		    description "UNI attributes information";
		  }
	   }
	 }
                
	  container service {
	    description "L1VC service";
	      list service-list {
             key "subscriber-l1vc-id";
             description
               "an unique identifier of a service";

               leaf subscriber-l1vc-id {
                 type string;
                 description "a unique service identifier for 
                            L1VC.";
               }
               container service-config {
                 description "service-config container";
                   uses subscriber-attributes;
		    }//end of service-config
	  }//end of service list
	    } //end of service container 		
  }//service top container
}
