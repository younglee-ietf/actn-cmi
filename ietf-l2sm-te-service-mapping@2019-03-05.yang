module ietf-l2sm-te-service-mapping {

       namespace "urn:ietf:params:xml:ns:yang:ietf-l2sm-te-service-mapping";

       prefix "tm";

       import ietf-te-service-mapping-types {
	  prefix "tsm-types";
       }
	   
       import ietf-l2vpn-svc {
          prefix "l2vpn-svc";
       }

       organization
           "IETF Traffic Engineering Architecture and Signaling (TEAS)
           Working Group";

       contact
           "Editor: Young Lee <leeyoung@huawei.com>
                    Dhruv Dhody <dhruv.ietf@gmail.com>
		            Qin Wu <bill.wu@huawei.com>";
       description
           "This module contains a YANG module for the mapping of
           Layer 2 Service Model (L1CSM) to the TE and VN ";

       revision 2019-03-05 {
           description
               "initial version.";
           reference
               "TBD";
       }

       /*
        * Configuration data nodes
        */
       augment "/l2vpn-svc:l2vpn-svc/l2vpn-svc:vpn-services/l2vpn-svc:vpn-service" {
	 description
           "l2sm augmented to include TE parameters and mapping";
	 container te-service-mapping {
         presence "indicates l2 service to te mapping";
           description
             "Container to augment l2sm to TE parameters and mapping";	
         }
       }
	   
       augment "/l2vpn-svc:l2vpn-svc/l2vpn-svc:vpn-services/l2vpn-svc:vpn-service" {
         description 
           "This augment is only valid for TE mapping --
            te mapping is added"; 
         uses tsm-types:te-mapping;
       }
	   
       augment "/l2vpn-svc:l2vpn-svc/l2vpn-svc:sites/l2vpn-svc:site"
	      +"/l2vpn-svc:site-network-accesses/l2vpn-svc:site-network-access" {
	 description 
           "This augment is only valid for TE mapping --
            network-access te-reference is added"; 
	 uses tsm-types:te-endpoint-ref;
       }
   }
