module ietf-actn-te-kpi-telemetry {

    namespace "urn:ietf:params:xml:ns:yang:ietf-actn-te-kpi-telemetry";

    prefix "actn-tel";

    import ietf-actn-vn {
        prefix "actn-vn";
    }
    
    import ietf-te {
        prefix "te";
    }

    import ietf-te-types {
		prefix "te-types"; 
    }

    import ietf-te-kpi-telemetry {
        prefix "te-kpi";
    }

    organization
        "IETF Traffic Engineering Architecture and Signaling (TEAS)
        Working Group";

    contact
        "Editor: Young Lee <leeyoung@huawei.com>
         Editor: Dhruv Dhody <dhruv.ietf@gmail.com>
         Editor: Ricard Vilalta <ricard.vilalta@cttc.es>
         Editor: Satish Karunanithi <satish.karunanithi@gmail.com>";

    description
        "This module describes telemetry for actn vn model";
    
    
    revision 2018-05-15 {
        description
            "Initial revision. This YANG file defines
            the ACTN VN telemetry.";
        reference
            "Derived from earlier versions of base YANG files";
    }

    /*
     * Typedefs
     */
    
    typedef grouping-operation {
	    
        type enumeration {
            enum MINIMUM { description "Select the minimum param"; }
            enum MAXIMUM { description "Select the maximum param"; }
            enum MEAN { description "Select the MEAN of the params"; }
            enum STD_DEV { description "Select the standard deviation of the monitored params"; }
            enum AND { description "Select the AND of the params"; }
            enum OR { description "Select the OR of the params"; }
        }  
		description 
			"Operations to analize list of monitored params";
    }   
	

   
    /*
     * Groupings
     */
    grouping vn-telemetry-param {
        description "augment of te-kpi:telemetry-param for VN specific params";
        
       
        leaf-list te-grouped-params {
            type leafref{
                path '/te:te/te:tunnels/te:tunnel/'+
                'te-kpi:te-telemetry/te-kpi:id';
            }
            description 
                "Allows the definition of a vn-telemetry param 
                as a grouping of underlying TE params";
        }

        leaf grouping-operation { 
            type grouping-operation; 
            description "describes the operation to apply to te-grouped-params"; 
        }
    
    }

    /*
     * Augments
     */

    augment "/actn-vn:actn/actn-vn:vn/actn-vn:vn-list" {

        description
            "Augmentation parameters for state TE VN topologies.";


        container vn-scaling-intent {
            description
                "scaling intent";

            container scale-in-intent{
                description
                    "VN scale-in";
                uses te-kpi:scaling-intent;
            }
            container scale-out-intent{
                description
                    "VN scale-out";                
                uses te-kpi:scaling-intent;
            }
        }    
        container vn-telemetry {
            config false;
            description
                "VN telemetry params";
            
            uses te-types:performance-metric-attributes; 
            uses te-kpi:bidirectional-telemetry-data;
            leaf grouping-operation { 
                type grouping-operation; 
                description "describes the operation to apply to the VN-members"; 
            }
        }            
    }

    /*
     * VN-member augment
     */
    augment "/actn-vn:actn/actn-vn:vn/actn-vn:vn-list/actn-vn:vn-member-list" {
        description
            "Augmentation parameters for state TE vn member topologies.";
        container vn-member-telemetry {
		    config false;
        	description
        		"VN member telemetry params";
        	
			uses te-types:performance-metric-attributes; 
			uses te-kpi:bidirectional-telemetry-data;
			uses vn-telemetry-param;
        }
    }


}
